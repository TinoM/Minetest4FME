FME workspace Minetest_Reader.fmw

Parameters:
- sqlite = C:\bin\minetest-0.4.10-win64\worlds\Small\map.sqlite   # Source SQLite Database File(s)
- pc = Yes   # Read as PointCloud
- player_pos:   # Python Script
      import re,fme,os
      
      def int64(u):
            while u >= 2**63:
                u -= 2**64
            while u <= -2**63:
                u += 2**64
            return u
      
      def getBlockAsInteger(p):
            return int64(p[2]*16777216 + p[1]*4096 + p[0])
      
      
      s = re.compile("position\s=\s\((.+),(.+),(.+)\)")
      with open(os.path.join(os.path.dirname(fme.macroValues['sqlite']),"players","singleplayer"),"r") as playerfile:
          for line in playerfile:
              res = s.match(line)
              if res:
                  player_x = int(float(res.group(1))/10.0)/16
                  player_y = int(float(res.group(2))/10.0)/16
                  player_z = int(float(res.group(3))/10.0)/16
                  blocks = []
                  if FME_MacroValues['pc'] == "No":
                      for i in xrange(player_x-1,player_x+1):
                          for j in xrange(player_z-1,player_z+1):
                              for k in xrange(player_y,player_y+2):
                                  blocks.append(str(getBlockAsInteger([i,k,j])))
                  else:
                      for i in xrange(player_x-6,player_x+6):
                          for j in xrange(player_z-6,player_z+6):
                              for k in xrange(player_y-2,player_y+2):
                                  blocks.append(str(getBlockAsInteger([i,k,j])))
                  a = "pos in (%s)" % ",".join(blocks)
                  return a

Readers:
- SQLITE3_1: SQLITE3 from $(sqlite)

blocks (reader SQLITE3_1)
    attributes: pos integer, data blob
    -> PythonCaller
PythonCaller
    NEW_ATTRIBUTES = content pos color_red color_blue color_green
    PYTHONSYMBOL = Process.FeatureProcessor
    -> Tester
Tester
    TEST_DESCRIPTION = ""
    TEST_CLAUSE = TEST $(pc) = No
    TEST_MODE = Automatic
    BOOL_OP = OR
    PASSED -> Map
    FAILED -> PointCloudCombiner
PointCloudCombiner
    SPACING = 1.0
    EXTRACT_RASTER_NODATA_NAME = No
    ACCUM_ATTRS_NAME = Yes
    ATTRS_TO_PRESERVE = color_red,UInt8,color_green,UInt8,color_blue,UInt8
    -> Map
Map: Inspector
